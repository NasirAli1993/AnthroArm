from pathlib import Path
import traceback
try:
    Path(r'D:\RoboticArm\results\anatomical_cad_error.txt').unlink(missing_ok=True)
    Path(r'D:\RoboticArm\results\anatomical_build_progress.txt').write_text('',encoding='utf-8')
    exec(compile(Path(r'D:\RoboticArm\design\build_anatomical_cad.py').read_text(encoding='utf-8'),r'D:\RoboticArm\design\build_anatomical_cad.py','exec'))
except Exception:
    Path(r'D:\RoboticArm\results\anatomical_cad_error.txt').write_text(traceback.format_exc(),encoding='utf-8')
    raise
