from pathlib import Path
import traceback
try:
 Path(r'D:\RoboticArm\results\v3\printable_finger_error.txt').unlink(missing_ok=True)
 exec(compile(Path(r'D:\RoboticArm\design\v3\build_printable_finger.py').read_text(encoding='utf-8'),r'D:\RoboticArm\design\v3\build_printable_finger.py','exec'))
except Exception:
 Path(r'D:\RoboticArm\results\v3\printable_finger_error.txt').write_text(traceback.format_exc(),encoding='utf-8');raise
